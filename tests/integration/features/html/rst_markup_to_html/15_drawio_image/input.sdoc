[DOCUMENT]
TITLE: Hello world doc

[TEXT]
STATEMENT: >>>
.. drawio-image:: _assets/diagram.drawio
<<<

[TEXT]
STATEMENT: >>>
.. drawio-image:: _assets/diagram.drawio
   :page: pagerino
   :limit: eERzdUeXhqdjQ1jmuvG7-1
<<<
